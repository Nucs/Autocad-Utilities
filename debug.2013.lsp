(command "_netload" "C:/Users/Eli/Desktop/autocad/autoload/autonet2013/bin/Debug/autonet.addons.dll")
;;(command "_netload" "%USERPROFILE%/Documents/C#/autonet/autonet/bin/Release/autonet.dll")
;;(command "_netload" "%USERPROFILE%/Documents/C#/autonet/autonet/bin/Release/autonet.dll")
