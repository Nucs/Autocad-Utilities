(command "_netload" "C:/Users/Eli/Desktop/autocad/autoload/autonet/bin/Debug/autonet.dll")
(command "_netload" "Z:/AutoCAD/C#/autonet/autonet/bin/Debug/autonet.dll")
(command "_netload" "C:/Users/Eli/Desktop/autocad/autoload/LispDebugAssistant/bin/Debug/LispDebugAssistant.dll")
;;(command "_netload" "%USERPROFILE%/Documents/C#/autonet/autonet/bin/Release/autonet.dll")
